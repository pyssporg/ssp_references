package SignalSineGainAdd {
  private import ScalarValues::*;
  private import PysspCore::*;

  part def System :> SspModel {
    attribute pyssp_default_start_time : Real = 0.0;
    attribute pyssp_default_stop_time : Real = 1.0;
    part sine : Sine;
    part step : Step;
    part gain : Gain;
    part add : Add;
    connect sine.y to gain.u;
    connect gain.y to add.u1;
    connect step.y to add.u2;
  }
}
