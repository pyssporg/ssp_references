package SignalStepAdd {
  private import ScalarValues::*;
  private import PysspCore::*;

  part def System :> SspModel {
    attribute pyssp_default_start_time : Real = 0.0;
    attribute pyssp_default_stop_time : Real = 1.0;
    part step_a : Step;
    part step_b : Step;
    part add : Add;
    connect step_a.y to add.u1;
    connect step_b.y to add.u2;
  }
}
