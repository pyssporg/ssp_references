// Generated by `pyssp generate sysml` from
// artifacts/models/signal_step_gain/baseline/SystemStructure.ssd.
// Evaluation artifact, not a build input. `pyssp generate ssd` now
// round-trips the pyssp_* control attributes back to SSD metadata.
package RecoveredFromSSD {
  port def Port_1 {
    attribute pyssp_flat_connector : Boolean = true;
    attribute value : Real;
  }

  part def Gain {
    attribute k : Real = 3.0;
    attribute pyssp_implementation : String = "CoSimulation";
    in port u : Port_1;
    out port y : Port_1;
  }

  part def Step {
    attribute height : Real = 2.0;
    attribute offset : Real = 1.0;
    attribute pyssp_implementation : String = "CoSimulation";
    attribute startTime : Real = 0.25;
    out port y : Port_1;
  }

  part def system {
    attribute pyssp_default_start_time : Real = 0.0;
    attribute pyssp_default_stop_time : Real = 1.0;
    attribute pyssp_parameter_set : String = "resources/signal_step_gain_parameters.ssv";
    part gain : Gain;
    part step : Step;
    connect step.y to gain.u;
  }
}
